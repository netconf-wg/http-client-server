module ietf-http-client {
  yang-version 1.1;
  namespace "urn:ietf:params:xml:ns:yang:ietf-http-client";
  prefix httpc;

  import ietf-inet-types {
    prefix inet;
    reference
      "RFC 6991: Common YANG Data Types";
  }

  import ietf-netconf-acm {
    prefix nacm;
    reference
      "RFC 8341: Network Configuration Access Control Model";
  }
  import ietf-tls-client {
    prefix tlsc;
    reference
      "RFC FFFF: YANG Groupings for TLS Clients and TLS Servers";
  }

  import iana-http-versions {
    prefix httpv;
    reference
      "RFC GGGG: YANG Groupings for HTTP Clients and HTTP Servers";
  }

  organization
    "IETF NETCONF (Network Configuration) Working Group";

  contact
    "WG Web:   https://datatracker.ietf.org/wg/netconf
     WG List:  NETCONF WG list <mailto:netconf@ietf.org>
     Author:   Kent Watsen <mailto:kent+ietf@watsen.net>";

  description
    "This module defines groupings for HTTP clients that can
     be used as a basis for specific HTTP client instances.

     Copyright (c) 2026 IETF Trust and the persons identified
     as authors of the code. All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     This version of this YANG module is part of RFC GGGG
     (https://www.rfc-editor.org/info/rfcGGGG); see the RFC
     itself for full legal notices.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.";

  revision YYYY-MM-DD {
    description
      "Initial version";
    reference
      "RFC GGGG: YANG Groupings for HTTP Clients and HTTP Servers";
  }

  // Features

  feature proxy-connect {
    description
      "Indicates that the server supports configuring HTTP
       clients to connect to a remote HTTP server via a
       proxy, per Section 9.3.6 of RFC 9110.";
    reference
      "RFC 9110: HTTP Semantics";
  }

  feature version-discovery {
    description
      "Indicates that the server implements the discovery for
       which HTTP versions are supported for HTTP clients.";
  }

  // Groupings

  grouping http-client-grouping {
    description
      "A grouping for HTTP client level configuration. This grouping
       is not expected to be used with groupings for lower protocol
       layer (e.g., the 'tcp-client-grouping' found in RFC 9643), as
       equivalent information is encoded into the URI.";
    reference
      "RFC 9643: YANG Groupings for TCP Clients and TCP Servers";

    container uri {
      must "scheme != 'https' or ../tls-client-parameters";
      description
        "The URI, described in Section 3 of RFC 3986, the HTTP client
         establishes a connection to.";
      reference
        "RFC 3986  URI Generic Syntax";
      leaf scheme {
        type string;
        mandatory true;
        description
          "The 'Scheme' as described in Section 3.1 of RFC 3986.";
      }
      container authority {
        presence
          "Indicates that 'authority' has been configured.";
        description
          "The 'Authority' as described in Section 3.2 of RFC 3986.";
        leaf userinfo {
          nacm:default-deny-all;
          type string;
          description
            "The 'User Information' as described in Section 3.2.1
             of RFC 3986.";
        }
        leaf host {
          type inet:host;
          mandatory true;
          description
            "The 'Host' as described in Section 3.2.2 of RFC 3986.";
        }
        leaf port {
          type inet:port-number;
          description
            "The 'Port' as described in Section 3.2.3 of RFC 3986.";
        }
      }
      leaf path {
        type string;
        description
          "The 'Path' as described in Section 3.3 of RFC 3986.";
      }
      leaf query {
        type string;
        description
          "The 'Query' as described in Section 3.4 of RFC 3986.";
      }
      leaf fragment {
        type string;
        description
          "The 'Fragment' as described in Section 3.5 of RFC 3986.";
      }
    }

    container protocol-versions {
      presence
        "If unconfigured, all supported HTTP versions are
         acceptable.";
      description
        "HTTP protocol versions the client accepts.";
      leaf-list protocol-version {
        type httpv:http-protocol-version;
        min-elements 1;
        description
          "Indicates that the client is configured to support
           this HTTP version.  The value must be one of the
           'supported-versions' values.";
      }
    } // container protocol-versions

    container tls-client-parameters {
      presence
        "Indicates that TLS-client parameters have been configured.";
      description
        "TLS client parameters for 'https' connections.";
      uses tlsc:tls-client-grouping;
    }

    container proxy-connect {
      if-feature proxy-connect;
      presence
        "Indicates that the HTTP-client connects through the
         configured proxy.";
      description
        "Configures how to connect to the proxy.";
      leaf protocol {
        type enumeration {
          enum CONNECT {
            description
              "Use the 'CONNECT' method described in Section 9.3.6
               of RFC 9110.";
            reference
              "RFC 9110: HTTP Semantics";
          }
          enum CONNECT-UDP {
            description
              "Use the 'connect-udp' upgrade token described in
               Section 3 of RFC 9298.";
            reference
              "RFC 9298: Proxying UDP in HTTP";
          }
        }
        mandatory true;
        description
          "The protocol to use when connecting to the proxy.";
      }
      leaf host {
        type inet:host;
        mandatory true;
        description
          "The 'Host' subcomponent, as described in Section 3.2.2 of
           RFC 3986, of the proxy.";
        reference
          "RFC 3986  URI Generic Syntax";
      }
      leaf port {
        type uint16;
        mandatory true;
        description
          "The 'Port' subcomponent, as described in Section 3.2.3 of
           RFC 3986, of the proxy.";
        reference
          "RFC 3986  URI Generic Syntax";
      }
    }

    container supported-versions {
      if-feature "version-discovery";
      config false;
      description
        "A container for a list of HTTP protocol versions supported
         by the client.";
      leaf-list supported-version {
        type httpv:http-protocol-version;
        description
          "An HTTP protocol version supported by the client.";
      }
    }

  } // http-client-grouping

}
